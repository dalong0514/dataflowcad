;冯大龙编于2020年
(princ "\n数据流一体化开发者：冯大龙、谢雨东、华雷、靳淳、陈杰，版本号V-0.7")
(princ "\n工艺专业：暖通全面通风条件数据提取命令：nsglobal")
(princ "\n工艺专业：做「电气条件」数据提取命令：gselectric")
(princ "\n工艺专业：做「仪表条件」数据提取命令：gsinstrument")
(princ "\n工艺专业：做「外管条件」数据提取命令：gsouterpipe")
(princ "\n工艺专业：做「设备一览表」数据提取命令：gsequipment")
(princ "\n工艺专业：流程图批量生成设备位号：equiptag")
(princ "\n工艺专业：做「管道特性表」数据提取命令：gspipe")
(vl-load-com)

; tansfor gb2312 to utf8
(defun file-encode-trans (file charset1 charset2 / obj encode)
  (setq obj (vlax-create-object "ADODB.Stream"))
  (vlax-put-property obj 'type 2);1-二进制读取，2-文本读取
  (vlax-put-property obj 'mode 3);1-读，2-写，3-读写
  (vlax-invoke obj 'open)
  (vlax-put-property obj "charset" charset1);;unicode;utf-8;ascii;gb2312;big5;gbk
  (vlax-invoke-method obj 'loadfromfile file)
  (setq encode (vlax-invoke obj 'readtext))
  (vlax-invoke obj 'close)
  (vlax-release-object obj)
  (setq obj (vlax-create-object "ADODB.Stream"))
  (vlax-put-property obj 'type 2)
  (vlax-put-property obj 'mode 3)
  (vlax-invoke obj 'open)
  (vlax-put-property obj "charset" charset2);;unicode;utf-8;ascii;gb2312;big5;gbk
  (vlax-invoke obj 'writetext encode)
  (vlax-invoke-method obj 'savetofile file 2);1-create，2-rewrite
  (vlax-invoke obj 'flush);将缓存中的数据强制输出
  (vlax-invoke obj 'close)
  (vlax-release-object obj)
)

; get the current file direction
(defun getFileDir (/ dcl_id fn currentDir)
  (setq dcl_id (load_dialog (strcat "D:\\dataflowcad\\" "dataflow.dcl")))
  (if (not (new_dialog "dataflow" dcl_id))
    (exit)
  )
  (set_tile "filename" "FileName");the default value of input box
  (mode_tile "filename" 2)
  (action_tile "filename" "(setq filename $value)")
  (action_tile "cancel" "(exit)")
  (action_tile "accept" "(done_dialog)")
  (start_dialog)
  (unload_dialog dcl_id)
  (setq fn filename)
  (setq currentDir (getvar "dwgprefix"))
  (setq fn (strcat currentDir fn ".txt"))
)

;  the command for print the newest version information
(defun c:printVersionInfo (/ versionInfo)
  (setq versionInfo "最新版本号 V0.7，更新时间：2020-10-10")
  (alert versionInfo)(princ)
)

; write the proptery of block to txt
(defun writeProperty (value captialName lowerName entx f / proptery)
  (if (= value captialName)
    (progn
      (setq proptery (cdr (assoc 1 entx)))
      (princ (strcat "\"" lowerName "\": \"" proptery "\",") f)
    )
  )
)

(defun c:EquipTag (/ insPt equipInfoList equipTag equipName i tag name)
  (setvar "ATTREQ" 1)
  (setvar "ATTDIA" 0)
  (setq ss (GetEquipSS))
  (setq equipInfoList (GetEquipTagList ss))
  (setq equipTag (car equipInfoList))
  (setq equipName (nth 1 equipInfoList))
  (setq insPt (getpoint "\n选取设备位号的插入点："))
  (setq i 0)
  (repeat (length equipTag) 
    (setq tag (nth i equipTag))
    (setq name (nth i equipName))
    (InsertEquipTag (GetInsPt insPt i) tag name)
    (setq i (+ 1 i))
  )
  (setvar "ATTREQ" 0)
)

; get the select set of equipment
(defun GetEquipSS ()
  (setq ss (ssget '((0 . "INSERT") 
		    (-4 . "<OR")
		      (2 . "Reactor")
		      (2 . "Pump")
		      (2 . "Tank")
		      (2 . "Heater")
		      (2 . "Centrifuge")
		      (2 . "Vacuum")
		      (2 . "CustomEquip")
		    (-4 . "OR>")
		   )
	   )
  )
)

; get the new inserting position
(defun GetInsPt (insPt i / xPosition yPosition newInsPt)
  (setq xPosition (+ (nth 0 insPt) (* i 30)))
  (setq yPosition (nth 1 insPt))
  (setq newInsPt (list xPosition yPosition))
)

; command for insert the equipment tag
(defun InsertEquipTag (insPt tag name / )
  (command "-insert" "EquipTag" insPt 1 1 0 tag name)
)

; modify property value of a block entity
(defun GetEquipTagList (ss / i ent blk entx value equipInfoList equipTag equipName)
  (if (/= ss nil)
    (progn
      (setq i 0)
      (setq equipTag '())
      (setq equipName '())
      (repeat (sslength ss)
        (if (/= nil (ssname ss i))
          (progn
	    ; get the entity information of the i(th) block
            (setq ent (entget (ssname ss i)))
	    ; save the entity name of the i(th) block
            (setq blk (ssname ss i))
	    ; get the property information
            (setq entx (entget (entnext (cdr (assoc -1 ent)))))
            (while (= "ATTRIB" (cdr (assoc 0 entx)))
              (setq value (cdr (assoc 2 entx)))
              (if (= value "TAG")
		(setq equipTag (append equipTag (list (cdr (assoc 1 entx)))))
              )
              (if (= value "NAME")
		(setq equipName (append equipName (list (cdr (assoc 1 entx)))))
              )
	      ; get the next property information
              (setq entx (entget (entnext (cdr (assoc -1 entx)))))
            )
            (entupd blk)
            (setq i (+ 1 i))
          )
        )
      )
    )
  )
  (setq equipInfoList (list equipTag equipName))
)

;  the command for extarcting data from the for PipeArrow Blocks
(defun c:gspipe (/ fn f ssLeft ssUp)
  (setq fn (getFileDir))
  (setq f (open fn "w"))
  (setq ssLeft (ssget "x" '((0 . "INSERT") (2 . "PipeArrowLeft"))))
  (setq ssUp (ssget "x" '((0 . "INSERT") (2 . "PipeArrowUp"))))
  (ExtactPipeArrow f ssLeft)
  (ExtactPipeArrow f ssUp)
  (close f)
  ; tansfor the encode
  (file-encode-trans fn "gb2312" "utf-8")
  (alert "数据提取成功")(princ)
)

; the command for extarcting data from globalVentilation Block
(defun c:nsglobal (/ fn f ssRoom ssSubstance ssHotWet)
  (setq fn (getFileDir))
  (setq f (open fn "w"))
  (setq ssRoom (ssget "x" '((0 . "INSERT") (2 . "RoomData"))))
  (setq ssSubstance (ssget "x" '((0 . "INSERT") (2 . "SubstanceData"))))
  (setq ssHotWet (ssget "x" '((0 . "INSERT") (2 . "HotWetData"))))
  (ExtactGlobalRoom f ssRoom)
  (ExtactGlobalSubstance f ssSubstance)
  (ExtactGlobalHotWet f ssHotWet)
  (close f)
  ; tansfor the encode
  (file-encode-trans fn "gb2312" "utf-8")
  (alert "数据提取成功")(princ)
)


; the command for extarcting data from InstrumentP/InstrumentL Block
(defun c:gsinstrument (/ fn f ssP ssL)
  (setq fn (getFileDir))
  (setq f (open fn "w"))
  (setq ssP (ssget "x" '((0 . "INSERT") (2 . "InstrumentP"))))
  (setq ssL (ssget "x" '((0 . "INSERT") (2 . "InstrumentL"))))
  (setq ssLeft (ssget "x" '((0 . "INSERT") (2 . "PipeArrowLeft"))))
  (setq ssUp (ssget "x" '((0 . "INSERT") (2 . "PipeArrowUp"))))
  (setq ssReactor (ssget "x" '((0 . "INSERT") (2 . "Reactor"))))
  (setq ssPump (ssget "x" '((0 . "INSERT") (2 . "Pump"))))
  (setq ssTank (ssget "x" '((0 . "INSERT") (2 . "Tank"))))
  (setq ssHeater (ssget "x" '((0 . "INSERT") (2 . "Heater"))))
  (setq ssCentrifuge (ssget "x" '((0 . "INSERT") (2 . "Centrifuge"))))
  (setq ssVacuum (ssget "x" '((0 . "INSERT") (2 . "Vacuum"))))
  (setq ssCustomEquip (ssget "x" '((0 . "INSERT") (2 . "CustomEquip"))))
  (ExtactInstrumentP f ssP)
  (ExtactInstrumentL f ssL)
  (ExtactPipeArrow f ssLeft)
  (ExtactPipeArrow f ssUp)
  (ExtactReactor f ssReactor)
  (ExtactPump f ssPump)
  (ExtactTank f ssTank)
  (ExtactHeater f ssHeater)
  (ExtactCentrifuge f ssCentrifuge)
  (ExtactVacuum f ssVacuum)
  (ExtactCustomEquip f ssCustomEquip)
  (close f)
  ; tansfor the encode
  (file-encode-trans fn "gb2312" "utf-8")
  (alert "数据提取成功")(princ)
)

; the command for extarcting data from Equipment Block
(defun c:gsequipment (/ fn f ssReactor ssPump ssTank ssHeater ssCentrifuge ssVacuum ssCustom)
  (setq fn (getFileDir))
  (setq f (open fn "w"))
  (setq ssReactor (ssget "x" '((0 . "INSERT") (2 . "Reactor"))))
  (setq ssPump (ssget "x" '((0 . "INSERT") (2 . "Pump"))))
  (setq ssTank (ssget "x" '((0 . "INSERT") (2 . "Tank"))))
  (setq ssHeater (ssget "x" '((0 . "INSERT") (2 . "Heater"))))
  (setq ssCentrifuge (ssget "x" '((0 . "INSERT") (2 . "Centrifuge"))))
  (setq ssVacuum (ssget "x" '((0 . "INSERT") (2 . "Vacuum"))))
  (setq ssCustomEquip (ssget "x" '((0 . "INSERT") (2 . "CustomEquip"))))
  (ExtactReactor f ssReactor)
  (ExtactPump f ssPump)
  (ExtactTank f ssTank)
  (ExtactHeater f ssHeater)
  (ExtactCentrifuge f ssCentrifuge)
  (ExtactVacuum f ssVacuum)
  (ExtactCustomEquip f ssCustomEquip)
  (close f)
  ; tansfor the encode
  (file-encode-trans fn "gb2312" "utf-8")
  (alert "数据提取成功")(princ)
)

; extarcting data from Equipment Block for electric condition
(defun c:gselectric (/ fn f ssReactor ssPump ssCentrifuge ssVacuum)
  (setq fn (getFileDir))
  (setq f (open fn "w"))
  (setq ssReactor (ssget "x" '((0 . "INSERT") (2 . "Reactor"))))
  (setq ssPump (ssget "x" '((0 . "INSERT") (2 . "Pump"))))
  (setq ssCentrifuge (ssget "x" '((0 . "INSERT") (2 . "Centrifuge"))))
  (setq ssVacuum (ssget "x" '((0 . "INSERT") (2 . "Vacuum"))))
  (ExtactReactor f ssReactor)
  (ExtactPump f ssPump)
  (ExtactCentrifuge f ssCentrifuge)
  (ExtactVacuum f ssVacuum)
  (close f)
  ; tansfor the encode
  (file-encode-trans fn "gb2312" "utf-8")
  (alert "数据提取成功")(princ)
)

; the command for extarcting data from OuterPipe Block
(defun c:gsouterpipe (/ fn f ssRightTo ssRightFrom ssLeftTo ssLeftFrom)
  (setq fn (getFileDir))
  (setq f (open fn "w"))
  (setq ssOuterPipeRight (ssget "x" '((0 . "INSERT") (2 . "OuterPipeRight"))))
  (setq ssOuterPipeLeft (ssget "x" '((0 . "INSERT") (2 . "OuterPipeLeft"))))
  (setq ssLeft (ssget "x" '((0 . "INSERT") (2 . "PipeArrowLeft"))))
  (setq ssUp (ssget "x" '((0 . "INSERT") (2 . "PipeArrowUp"))))
  (ExtactOuterPipe f ssOuterPipeRight)
  (ExtactOuterPipe f ssOuterPipeLeft)
  (ExtactPipeArrow f ssLeft)
  (ExtactPipeArrow f ssUp)
  (close f)
  ; tansfor the encode
  (file-encode-trans fn "gb2312" "utf-8")
  (alert "数据提取成功")(princ)
)

; extarct data form the for OuterPipe Blocks
(defun ExtactOuterPipe (f ss / N index i ent blk entx value)
  (if (/= ss nil)
    (progn
      (setq N (sslength ss))
      (setq index 0)
      (setq i index)
      (repeat N
        (if (/= nil (ssname ss i))
          (progn
            (princ "{" f)
            (setq ent (entget (ssname ss i)))
            (setq blk (ssname ss i))
            (setq entx (entget (entnext (cdr (assoc -1 ent)))))
            (while (= "ATTRIB" (cdr (assoc 0 entx)))
              (setq value (cdr (assoc 2 entx)))
              (writeProperty value "PIPENUM" "pipenum" entx f)
              (writeProperty value "FROMTO" "fromto" entx f)
              (writeProperty value "DWGNUM" "dwgnum" entx f)
              (writeProperty value "DESIGNFLOW" "designflow" entx f)
              (writeProperty value "OPERATESPEC" "operatespec" entx f)
              (writeProperty value "INSULATION" "insulation" entx f)
              (if (= value "PROTECTION")
                (progn
                  (setq protection (cdr (assoc 1 entx)))
		  (princ (strcat "\"class\": \"" "outerpipe" "\",") f)
                  (princ (strcat "\"protection\": \"" protection "\"") f)
                )
              )
              ; 下面的语句必须设置，否则无限写数据
              (setq entx (entget (entnext (cdr (assoc -1 entx)))))
            )
            (princ "}\n" f)
            (entupd blk)
            (setq i (+ 1 i))
          )
        )
        (setq index (+ 1 index))
        (princ)
      )
    )
  )
)

; extarct data form Centrifuge Block
(defun ExtactCentrifuge (f ss / N index i ent blk entx value number)
  (if (/= ss nil)
    (progn
      (setq N (sslength ss))
      (setq index 0)
      (setq i index)
      (repeat N
        (if (/= nil (ssname ss i))
          (progn
            (princ "{" f)
            (setq ent (entget (ssname ss i)))
            (setq blk (ssname ss i))
            (setq entx (entget (entnext (cdr (assoc -1 ent)))))
            (while (= "ATTRIB" (cdr (assoc 0 entx)))
              (setq value (cdr (assoc 2 entx)))
              (writeProperty value "TAG" "tag" entx f)
              (writeProperty value "NAME" "name" entx f)
              (writeProperty value "SPECIES" "first_spec" entx f)
              (writeProperty value "SUBSTANCE" "substance" entx f)
              (writeProperty value "TEMP" "temp" entx f)
              (writeProperty value "PRESSURE" "pressure" entx f)
              (writeProperty value "VOLUME" "volumn" entx f)
              (writeProperty value "CAPACITY" "capacity" entx f)
              (writeProperty value "DIAMETER" "diameter" entx f)
              (writeProperty value "SPEED" "speed" entx f)
              (writeProperty value "FACTOR" "factor" entx f)
              (writeProperty value "DIAMETER" "diameter" entx f)
	      (writeProperty value "SIZE" "size" entx f)
              (writeProperty value "POWER" "power" entx f)
              (writeProperty value "ANTIEXPLOSIVE" "is_antiexplosive" entx f)
              (writeProperty value "MOTORSERIES" "motorseries" entx f)
              (writeProperty value "MATERIAL" "material" entx f)
              (writeProperty value "WEIGHT" "weight" entx f)
              (writeProperty value "TYPE" "type" entx f)
              (if (= value "NUMBER")
                (progn
                  (setq number (cdr (assoc 1 entx)))
		  (princ (strcat "\"class\": \"" "centrifuge" "\",") f)
                  (princ (strcat "\"number\": \"" number "\"") f)
                )
              )
              ; 下面的语句必须设置，否则无限写数据
              (setq entx (entget (entnext (cdr (assoc -1 entx)))))
            )
            (princ "}\n" f)
            (entupd blk)
            (setq i (+ 1 i))
          )
        )
        (setq index (+ 1 index))
        (princ)
      )
    )
  )
)

; extarct data form Vacuum Block
(defun ExtactVacuum (f ss / N index i ent blk entx value number)
  (if (/= ss nil)
    (progn
      (setq N (sslength ss))
      (setq index 0)
      (setq i index)
      (repeat N
        (if (/= nil (ssname ss i))
          (progn
            (princ "{" f)
            (setq ent (entget (ssname ss i)))
            (setq blk (ssname ss i))
            (setq entx (entget (entnext (cdr (assoc -1 ent)))))
            (while (= "ATTRIB" (cdr (assoc 0 entx)))
              (setq value (cdr (assoc 2 entx)))
              (writeProperty value "TAG" "tag" entx f)
              (writeProperty value "NAME" "name" entx f)
              (writeProperty value "SPECIES" "first_spec" entx f)              
              (writeProperty value "SUBSTANCE" "substance" entx f)
              (writeProperty value "TEMP" "temp" entx f)
              (writeProperty value "PRESSURE" "pressure" entx f)
              (writeProperty value "CAPACITY" "capacity" entx f)
              (writeProperty value "EXPRESSURE" "expressure" entx f)
              (writeProperty value "POWER" "power" entx f)
              (writeProperty value "ANTIEXPLOSIVE" "is_antiexplosive" entx f)
              (writeProperty value "MOTORSERIES" "motorseries" entx f)
              (writeProperty value "SIZE" "size" entx f)
              (writeProperty value "MATERIAL" "material" entx f)
              (writeProperty value "WEIGHT" "weight" entx f)
              (writeProperty value "TYPE" "type" entx f)
              (if (= value "NUMBER")
                (progn
                  (setq number (cdr (assoc 1 entx)))
		  (princ (strcat "\"class\": \"" "vacuum" "\",") f)
                  (princ (strcat "\"number\": \"" number "\"") f)
                )
              )
              ; 下面的语句必须设置，否则无限写数据
              (setq entx (entget (entnext (cdr (assoc -1 entx)))))
            )
            (princ "}\n" f)
            (entupd blk)
            (setq i (+ 1 i))
          )
        )
        (setq index (+ 1 index))
        (princ)
      )
    )
  )
)

; extarct data form Heater Block
(defun ExtactHeater (f ss / N index i ent blk entx value number)
  (if (/= ss nil)
    (progn
      (setq N (sslength ss))
      (setq index 0)
      (setq i index)
      (repeat N
        (if (/= nil (ssname ss i))
          (progn
            (princ "{" f)
            (setq ent (entget (ssname ss i)))
            (setq blk (ssname ss i))
            (setq entx (entget (entnext (cdr (assoc -1 ent)))))
            (while (= "ATTRIB" (cdr (assoc 0 entx)))
              (setq value (cdr (assoc 2 entx)))
              (writeProperty value "TAG" "tag" entx f)
              (writeProperty value "NAME" "name" entx f)
              (writeProperty value "SPECIES" "first_spec" entx f)
              (writeProperty value "AREA" "area" entx f)
              (writeProperty value "SUBSTANCE" "substance" entx f)
              (writeProperty value "TEMP" "temp" entx f)
              (writeProperty value "PRESSURE" "pressure" entx f)
              (writeProperty value "SIZE" "size" entx f)
              (writeProperty value "ELEMENT" "element" entx f)
              (writeProperty value "MATERIAL" "material" entx f)
              (writeProperty value "WEIGHT" "weight" entx f)
              (writeProperty value "TYPE" "type" entx f)
              (writeProperty value "INSULATIONTHICK" "insulationthick" entx f)
              (if (= value "NUMBER")
                (progn
                  (setq number (cdr (assoc 1 entx)))
                  (princ (strcat "\"class\": \"" "heater" "\",") f)
                  (princ (strcat "\"number\": \"" number "\"") f)
                )
              )
              ; 下面的语句必须设置，否则无限写数据
              (setq entx (entget (entnext (cdr (assoc -1 entx)))))
            )
            (princ "}\n" f)
            (entupd blk)
            (setq i (+ 1 i))
          )
        )
        (setq index (+ 1 index))
        (princ)
      )
    )
  )
)

; extarct data form Tank Block
(defun ExtactTank (f ss / N index i ent blk entx value expressure)
  (if (/= ss nil)
    (progn
      (setq N (sslength ss))
      (setq index 0)
      (setq i index)
      (repeat N
        (if (/= nil (ssname ss i))
          (progn
            (princ "{" f)
            (setq ent (entget (ssname ss i)))
            (setq blk (ssname ss i))
            (setq entx (entget (entnext (cdr (assoc -1 ent)))))
            (while (= "ATTRIB" (cdr (assoc 0 entx)))
              (setq value (cdr (assoc 2 entx)))
              (writeProperty value "TAG" "tag" entx f)
              (writeProperty value "NAME" "name" entx f)
              (writeProperty value "SPECIES" "first_spec" entx f)
              (writeProperty value "VOLUME" "volumn" entx f)
              (writeProperty value "SUBSTANCE" "substance" entx f)
              (writeProperty value "TEMP" "temp" entx f)
              (writeProperty value "PRESSURE" "pressure" entx f)
              (writeProperty value "POWER" "power" entx f)
              (writeProperty value "ANTIEXPLOSIVE" "is_antiexplosive" entx f)
              (writeProperty value "MOTORSERIES" "motorseries" entx f)
              (writeProperty value "SIZE" "size" entx f)
              (writeProperty value "MATERIAL" "material" entx f)
              (writeProperty value "WEIGHT" "weight" entx f)
              (writeProperty value "TYPE" "type" entx f)
              (writeProperty value "INSULATIONTHICK" "insulationthick" entx f)
              (writeProperty value "NUMBER" "number" entx f)
              (writeProperty value "EXTEMP" "extemp" entx f)
              (if (= value "EXPRESSURE")
                (progn
                  (setq expressure (cdr (assoc 1 entx)))
                  (princ (strcat "\"class\": \"" "tank" "\",") f)
                  (princ (strcat "\"expressure\": \"" expressure "\"") f)
                )
              )
              ; 下面的语句必须设置，否则无限写数据
              (setq entx (entget (entnext (cdr (assoc -1 entx)))))
            )
            (princ "}\n" f)
            (entupd blk)
            (setq i (+ 1 i))
          )
        )
        (setq index (+ 1 index))
        (princ)
      )
    )
  )
)

; extarct data form Pump Block
(defun ExtactPump (f ss / N index i ent blk entx value equiptype)
  (if (/= ss nil)
    (progn
      (setq N (sslength ss))
      (setq index 0)
      (setq i index)
      (repeat N
        (if (/= nil (ssname ss i))
          (progn
            (princ "{" f)
            (setq ent (entget (ssname ss i)))
            (setq blk (ssname ss i))
            (setq entx (entget (entnext (cdr (assoc -1 ent)))))
            (while (= "ATTRIB" (cdr (assoc 0 entx)))
              (setq value (cdr (assoc 2 entx)))
              (writeProperty value "TAG" "tag" entx f)
              (writeProperty value "NAME" "name" entx f)
              (writeProperty value "SPECIES" "first_spec" entx f)
              (writeProperty value "SUBSTANCE" "substance" entx f)
              (writeProperty value "TEMP" "temp" entx f)
              (writeProperty value "PRESSURE" "pressure" entx f)
	      (writeProperty value "FLOW" "flow" entx f)
              (writeProperty value "HEAD" "head" entx f)
              (writeProperty value "POWER" "power" entx f)
              (writeProperty value "ANTIEXPLOSIVE" "is_antiexplosive" entx f)
              (writeProperty value "MOTORSERIES" "motorseries" entx f)
              (writeProperty value "MATERIAL" "material" entx f)
              (writeProperty value "WEIGHT" "weight" entx f)
              (writeProperty value "NUMBER" "number" entx f)
              (if (= value "TYPE")
                (progn
                  (setq equiptype (cdr (assoc 1 entx)))
                  (princ (strcat "\"class\": \"" "pump" "\",") f)
                  (princ (strcat "\"type\": \"" equiptype "\"") f)
                )
              )
              ; 下面的语句必须设置，否则无限写数据
              (setq entx (entget (entnext (cdr (assoc -1 entx)))))
            )
            (princ "}\n" f)
            (entupd blk)
            (setq i (+ 1 i))
          )
        )
        (setq index (+ 1 index))
        (princ)
      )
    )
  )
)

; extarct data form Reactor Block
(defun ExtactReactor (f ss / N index i ent blk entx value expressure)
  (if (/= ss nil)
    (progn
      (setq N (sslength ss))
      (setq index 0)
      (setq i index)
      (repeat N
        (if (/= nil (ssname ss i))
          (progn
            (princ "{" f)
            (setq ent (entget (ssname ss i)))
            (setq blk (ssname ss i))
            (setq entx (entget (entnext (cdr (assoc -1 ent)))))
            (while (= "ATTRIB" (cdr (assoc 0 entx)))
              (setq value (cdr (assoc 2 entx)))
              (writeProperty value "TAG" "tag" entx f)
              (writeProperty value "NAME" "name" entx f)
              (writeProperty value "VOLUME" "volumn" entx f)
              (writeProperty value "SPECIES" "first_spec" entx f)
              (writeProperty value "SUBSTANCE" "substance" entx f)
              (writeProperty value "TEMP" "temp" entx f)
              (writeProperty value "PRESSURE" "pressure" entx f)
              (writeProperty value "POWER" "power" entx f)
              (writeProperty value "ANTIEXPLOSIVE" "is_antiexplosive" entx f)
              (writeProperty value "MOTORSERIES" "motorseries" entx f)
              (writeProperty value "SIZE" "size" entx f)
              (writeProperty value "SPEED" "speed" entx f)
              (writeProperty value "MATERIAL" "material" entx f)
              (writeProperty value "WEIGHT" "weight" entx f)
              (writeProperty value "TYPE" "type" entx f)
              (writeProperty value "INSULATIONTHICK" "insulationthick" entx f)
              (writeProperty value "NUMBER" "number" entx f)
              (writeProperty value "EXTEMP" "extemp" entx f)
              (if (= value "EXPRESSURE")
                (progn
                  (setq expressure (cdr (assoc 1 entx)))
                  (princ (strcat "\"class\": \"" "reactor" "\",") f)
                  (princ (strcat "\"expressure\": \"" expressure "\"") f)
                )
              )
              ; 下面的语句必须设置，否则无限写数据
              (setq entx (entget (entnext (cdr (assoc -1 entx)))))
            )
            (princ "}\n" f)
            (entupd blk)
            (setq i (+ 1 i))
          )
        )
        (setq index (+ 1 index))
        (princ)
      )
    )
  )
)

; extarct data form CustomEquip Block
(defun ExtactCustomEquip (f ss / N index i ent blk entx value number)
  (if (/= ss nil)
    (progn
      (setq N (sslength ss))
      (setq index 0)
      (setq i index)
      (repeat N
        (if (/= nil (ssname ss i))
          (progn
            (princ "{" f)
            (setq ent (entget (ssname ss i)))
            (setq blk (ssname ss i))
            (setq entx (entget (entnext (cdr (assoc -1 ent)))))
            (while (= "ATTRIB" (cdr (assoc 0 entx)))
              (setq value (cdr (assoc 2 entx)))
              (writeProperty value "TAG" "tag" entx f)
              (writeProperty value "NAME" "name" entx f)
              (writeProperty value "SPECIES" "first_spec" entx f)
              (writeProperty value "SUBSTANCE" "substance" entx f)
              (writeProperty value "TEMP" "temp" entx f)
              (writeProperty value "PRESSURE" "pressure" entx f)
              (writeProperty value "POWER" "power" entx f)
              (writeProperty value "ANTIEXPLOSIVE" "is_antiexplosive" entx f)
              (writeProperty value "MOTORSERIES" "motorseries" entx f)
              (writeProperty value "PARAM1" "param1" entx f)
              (writeProperty value "PARAM2" "param2" entx f)
              (writeProperty value "PARAM3" "param3" entx f)
              (writeProperty value "PARAM4" "param4" entx f)
              (writeProperty value "SIZE" "size" entx f)
              (writeProperty value "MATERIAL" "material" entx f)
              (writeProperty value "WEIGHT" "weight" entx f)
              (writeProperty value "TYPE" "type" entx f)
              (writeProperty value "INSULATIONTHICK" "insulationthick" entx f)
              (if (= value "NUMBER")
                (progn
                  (setq number (cdr (assoc 1 entx)))
                  (princ (strcat "\"class\": \"" "custom" "\",") f)
                  (princ (strcat "\"number\": \"" number "\"") f)
                )
              )
              ; 下面的语句必须设置，否则无限写数据
              (setq entx (entget (entnext (cdr (assoc -1 entx)))))
            )
            (princ "}\n" f)
            (entupd blk)
            (setq i (+ 1 i))
          )
        )
        (setq index (+ 1 index))
        (princ)
      )
    )
  )
)

; extarct data form InstrumentL Block
(defun ExtactInstrumentL (f ss / N index i ent blk entx value nomal)
  (if (/= ss nil)
    (progn
      (setq N (sslength ss))
      (setq index 0)
      (setq i index)
      (repeat N
        (if (/= nil (ssname ss i))
          (progn
            (princ "{" f)
            (setq ent (entget (ssname ss i)))
            (setq blk (ssname ss i))
            (setq entx (entget (entnext (cdr (assoc -1 ent)))))
            (while (= "ATTRIB" (cdr (assoc 0 entx)))
              (setq value (cdr (assoc 2 entx)))
              (writeProperty value "FUNCTION" "function" entx f)
              (writeProperty value "TAG" "tag" entx f)
              (writeProperty value "SUBSTANCE" "substance" entx f)
              (writeProperty value "TEMP" "temp" entx f)
              (writeProperty value "PRESSURE" "pressure" entx f)
	      (writeProperty value "SORT" "sort" entx f)
              (writeProperty value "PHASE" "phase" entx f)
              (writeProperty value "MATERIAL" "material" entx f)
              (writeProperty value "NAME" "name" entx f)
              (writeProperty value "LOCATION" "location" entx f)
              (writeProperty value "MIN" "minvalue" entx f)
              (writeProperty value "MAX" "maxvalue" entx f)
	      (writeProperty value "NOMAL" "nomal" entx f)
	      (writeProperty value "DRAWNUM" "drawnum" entx f)
	      (writeProperty value "COMMENT" "comment" entx f)
	      (writeProperty value "INSTALLSIZE" "installsize" entx f)
              (if (= value "DIRECTION")
                (progn
                  (setq direction (cdr (assoc 1 entx)))
                  (princ (strcat "\"class\": \"" "location" "\",") f)
                  (princ (strcat "\"direction\": \"" direction "\"") f)
                )
              )
              ; 下面的语句必须设置，否则无限写数据
              (setq entx (entget (entnext (cdr (assoc -1 entx)))))
            )
            (princ "}\n" f)
            (entupd blk)
            (setq i (+ 1 i))
          )
        )
        (setq index (+ 1 index))
        (princ)
      )
    )
  )
)

; extarct data form InstrumentP Block
(defun ExtactInstrumentP (f ss / N index i ent blk entx value nomal)
  (if (/= ss nil)
    (progn
      (setq N (sslength ss))
      (setq index 0)
      (setq i index)
      (repeat N
        (if (/= nil (ssname ss i))
          (progn
            (princ "{" f)
            (setq ent (entget (ssname ss i)))
            (setq blk (ssname ss i))
            (setq entx (entget (entnext (cdr (assoc -1 ent)))))
            (while (= "ATTRIB" (cdr (assoc 0 entx)))
              (setq value (cdr (assoc 2 entx)))
              (writeProperty value "FUNCTION" "function" entx f)
              (writeProperty value "TAG" "tag" entx f)
              (writeProperty value "HALARM" "halarm" entx f)
              (writeProperty value "LALARM" "lalarm" entx f)
              (writeProperty value "SUBSTANCE" "substance" entx f)
              (writeProperty value "TEMP" "temp" entx f)
              (writeProperty value "PRESSURE" "pressure" entx f)
	      (writeProperty value "SORT" "sort" entx f)
              (writeProperty value "PHASE" "phase" entx f)
              (writeProperty value "MATERIAL" "material" entx f)
              (writeProperty value "NAME" "name" entx f)
              (writeProperty value "LOCATION" "location" entx f)
              (writeProperty value "MIN" "minvalue" entx f)
              (writeProperty value "MAX" "maxvalue" entx f)
	      (writeProperty value "NOMAL" "nomal" entx f)
	      (writeProperty value "DRAWNUM" "drawnum" entx f)
	      (writeProperty value "COMMENT" "comment" entx f)
	      (writeProperty value "INSTALLSIZE" "installsize" entx f)
              (if (= value "DIRECTION")
                (progn
                  (setq direction (cdr (assoc 1 entx)))
                  (princ (strcat "\"class\": \"" "concentrated" "\",") f)
                  (princ (strcat "\"direction\": \"" direction "\"") f)
                )
              )
              ; 下面的语句必须设置，否则无限写数据
              (setq entx (entget (entnext (cdr (assoc -1 entx)))))
            )
            (princ "}\n" f)
            (entupd blk)
            (setq i (+ 1 i))
          )
        )
        (setq index (+ 1 index))
        (princ)
      )
    )
  )
)

; extarct data form HotWetData Block
(defun ExtactGlobalHotWet (f ss / N index i ent blk entx value water_temp)
  (if (/= ss nil)
    (progn
      (setq N (sslength ss))
      (setq index 0)
      (setq i index)
      (repeat N
        (if (/= nil (ssname ss i))
          (progn
            (princ "{" f)
            (setq ent (entget (ssname ss i)))
            (setq blk (ssname ss i))
            (setq entx (entget (entnext (cdr (assoc -1 ent)))))
            (while (= "ATTRIB" (cdr (assoc 0 entx)))
              (setq value (cdr (assoc 2 entx)))
              (writeProperty value "ROOM_NUM" "room_num" entx f)
              (writeProperty value "EQUIPMENT_NUM" "equipment_num" entx f)
              (writeProperty value "TYPE" "type" entx f)
              (writeProperty value "AIR_EXHAUST" "air_exhaust" entx f)
              (writeProperty value "PRESERVE_HEAT" "preserve_heat" entx f)
              (writeProperty value "POWER" "power" entx f)
              (writeProperty value "SURFACE_AREA" "surface_area" entx f)
              (writeProperty value "SURFACE_TEMP" "surface_temp" entx f)
              (writeProperty value "WATER_AREA" "water_area" entx f)
              (if (= value "WATER_TEMP")
                (progn
                  (setq water_temp (cdr (assoc 1 entx)))
                  (princ (strcat "\"block_data\": \"" "hotwet" "\",") f)
                  (princ (strcat "\"water_temp\": \"" water_temp "\"") f)
                )
              )
              ; 下面的语句必须设置，否则无限写数据
              (setq entx (entget (entnext (cdr (assoc -1 entx)))))
            )
            (princ "}\n" f)
            (entupd blk)
            (setq i (+ 1 i))
          )
        )
        (setq index (+ 1 index))
        (princ)
      )
    )
  )
)

; extarct data form SubstanceData Block
(defun ExtactGlobalSubstance (f ss / N index i ent blk entx value compress_num)
  (if (/= ss nil)
    (progn
      (setq N (sslength ss))
      (setq index 0)
      (setq i index)
      (repeat N
        (if (/= nil (ssname ss i))
          (progn
            (princ "{" f)
            (setq ent (entget (ssname ss i)))
            (setq blk (ssname ss i))
            (setq entx (entget (entnext (cdr (assoc -1 ent)))))
            (while (= "ATTRIB" (cdr (assoc 0 entx)))
              (setq value (cdr (assoc 2 entx)))
              (writeProperty value "ROOM_NUM" "room_num" entx f)
              (writeProperty value "SUBSTANCE_NAME" "substance_name" entx f)
              (writeProperty value "VALUE_NUM" "value_num" entx f)
              (writeProperty value "PUMPSEAL_NUM" "pumpseal_num" entx f)
              (writeProperty value "FLANGE_NUM" "flange_num" entx f)
              (writeProperty value "DISCHARGE_NUM" "discharge_num" entx f)
              (writeProperty value "SAFETY_NUM" "safety_num" entx f)
              (if (= value "COMPRESS_NUM")
                (progn
                  (setq compress_num (cdr (assoc 1 entx)))
                  (princ (strcat "\"block_data\": \"" "substance" "\",") f)
                  (princ (strcat "\"compress_num\": \"" compress_num "\"") f)
                )
              )
              ; 下面的语句必须设置，否则无限写数据
              (setq entx (entget (entnext (cdr (assoc -1 entx)))))
            )
            (princ "}\n" f)
            (entupd blk)
            (setq i (+ 1 i))
          )
        )
        (setq index (+ 1 index))
        (princ)
      )
    )
  )
)

; extarct data form RoomData Block
(defun ExtactGlobalRoom (f ss / N index i ent blk entx value winter_rehumidity)
  (if (/= ss nil)
    (progn
      (setq N (sslength ss))
      (setq index 0)
      (setq i index)
      (repeat N
        (if (/= nil (ssname ss i))
          (progn
            (princ "{" f)
            (setq ent (entget (ssname ss i)))
            (setq blk (ssname ss i))
            (setq entx (entget (entnext (cdr (assoc -1 ent)))))
            (while (= "ATTRIB" (cdr (assoc 0 entx)))
              (setq value (cdr (assoc 2 entx)))
              (writeProperty value "ROOM_NUM" "room_num" entx f)
              (writeProperty value "ROOM_NAME" "room_name" entx f)
              (writeProperty value "ROOM_AREA" "room_area" entx f)
              (writeProperty value "ROOM_HEIGHT" "room_height" entx f)
              (writeProperty value "ROOM_PRESSURE" "room_pressure" entx f)
              (writeProperty value "SUMMER_TEMP" "summer_temp" entx f)
              (writeProperty value "SUMMER_REHUMIDITY" "summer_rehumidity" entx f)
              (writeProperty value "WINTER_TEMP" "winter_temp" entx f)
              (if (= value "WINTER_REHUMIDITY")
                (progn
                  (setq winter_rehumidity (cdr (assoc 1 entx)))
                  (princ (strcat "\"block_data\": \"" "room" "\",") f)
                  (princ (strcat "\"winter_rehumidity\": \"" winter_rehumidity "\"") f)
                )
              )
              ; 下面的语句必须设置，否则无限写数据
              (setq entx (entget (entnext (cdr (assoc -1 entx)))))
            )
            (princ "}\n" f)
            (entupd blk)
            (setq i (+ 1 i))
          )
        )
        (setq index (+ 1 index))
        (princ)
      )
    )
  )
)

; extarct data form the for PipeArrow Blocks
(defun ExtactPipeArrow (f ss / N index i ent blk entx value pipenum substance temp pressure phase fromP toP insulation)
  (if (/= ss nil)
    (progn
      (setq N (sslength ss))
      (setq index 0)
      (setq i index)
      (repeat N
        (if (/= nil (ssname ss i))
          (progn
            (princ "{" f)
            (setq ent (entget (ssname ss i)))
            (setq blk (ssname ss i))
            (setq entx (entget (entnext (cdr (assoc -1 ent)))))
            (while (= "ATTRIB" (cdr (assoc 0 entx)))
              (setq value (cdr (assoc 2 entx)))
              (writeProperty value "PIPENUM" "pipenum" entx f)
              (writeProperty value "SUBSTANCE" "substance" entx f)
              (writeProperty value "TEMP" "temp" entx f)
              (writeProperty value "PRESSURE" "pressure" entx f)
              (writeProperty value "PHASE" "phase" entx f)
              (writeProperty value "FROM" "from" entx f)
              (writeProperty value "TO" "to" entx f)
	      (writeProperty value "DRAWNUM" "drawnum" entx f)
              (if (= value "INSULATION")
                (progn
                  (setq insulation (cdr (assoc 1 entx)))
		  (princ (strcat "\"class\": \"" "pipeline" "\",") f)
                  (princ (strcat "\"insulation\": \"" insulation "\"") f)
                )
              )
              ; 下面的语句必须设置，否则无限写数据
              (setq entx (entget (entnext (cdr (assoc -1 entx)))))
            )
            (princ "}\n" f)
            (entupd blk)
            (setq i (+ 1 i))
          )
        )
        (setq index (+ 1 index))
        (princ)
      )
    )
  )
)
